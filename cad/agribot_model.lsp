;;; =========================================================================
;;; AgriBot-X Cyber Field Rover: High-Clearance Strut Architecture
;;; Native AutoCAD 3D Solid Model Generation AutoLISP (BUILD_AGRIBOT)
;;; =========================================================================

(defun c:BUILD_AGRIBOT ( / oldecho oldosmode)
  (setq oldecho (getvar "CMDECHO"))
  (setq oldosmode (getvar "OSMODE"))
  (setvar "CMDECHO" 0)
  (setvar "OSMODE" 0)
  
  (princ "\nInitializing AgriBot-X High-Clearance Strut Layers...")
  (command "-LAYER" "M" "CHASSIS" "C" "4" "CHASSIS" "")
  (command "-LAYER" "M" "WHEELS" "C" "8" "WHEELS" "")
  (command "-LAYER" "M" "MOTORS" "C" "6" "MOTORS" "")
  (command "-LAYER" "M" "CAMERA" "C" "4" "CAMERA" "")
  (command "-LAYER" "M" "SOIL_PROBE" "C" "2" "SOIL_PROBE" "")
  (command "-LAYER" "M" "SENSORS" "C" "3" "SENSORS" "")
  (command "-LAYER" "M" "ELECTRONICS" "C" "5" "ELECTRONICS" "")
  (command "-LAYER" "M" "BATTERY" "C" "30" "BATTERY" "")
  (command "-LAYER" "M" "NAVIGATION" "C" "7" "NAVIGATION" "")
  (command "-LAYER" "M" "DRONE_DOCK" "C" "140" "DRONE_DOCK" "")
  (command "-LAYER" "M" "DRONE" "C" "1" "DRONE" "")
  (command "-LAYER" "M" "SAFETY" "C" "1" "SAFETY" "")

  (princ "\nConstructing 3D Elevated Cyber Hull (Belly Clearance 420mm)...")
  (setvar "CLAYER" "CHASSIS")
  (command "BOX" '(-310.0 -170.0 420.0) '(310.0 170.0 490.0))
  (command "BOX" '(-330.0 -195.0 490.0) '(330.0 195.0 570.0))
  (command "BOX" '(-290.0 -140.0 570.0) '(290.0 140.0 670.0))
  (command "CYLINDER" '(355.0 -160.0 445.0) "14.0" "A" '(355.0 160.0 445.0))

  (princ "\nConstructing Front Electric-Blue LED Light Bar...")
  (setvar "CLAYER" "SAFETY")
  (command "BOX" '(330.0 -185.0 552.0) '(338.0 185.0 568.0))

  (princ "\nConstructing 4WD Tractor Wheels (Dia 340mm, Stance 680mm)...")
  (setvar "CLAYER" "WHEELS")
  (command "CYLINDER" '(210.0 217.5 170.0) "2D" "170.0" "A" '(210.0 322.5 170.0))
  (command "CYLINDER" '(210.0 -322.5 170.0) "2D" "170.0" "A" '(210.0 -217.5 170.0))
  (command "CYLINDER" '(-210.0 217.5 170.0) "2D" "170.0" "A" '(-210.0 322.5 170.0))
  (command "CYLINDER" '(-210.0 -322.5 170.0) "2D" "170.0" "A" '(-210.0 -217.5 170.0))

  (princ "\nConstructing Exposed Vertical Coilover Shock Struts...")
  (setvar "CLAYER" "SAFETY")
  (command "CYLINDER" '(220.0 235.0 240.0) "12.0" "280.0")
  (command "CYLINDER" '(220.0 -235.0 240.0) "12.0" "280.0")
  (command "CYLINDER" '(-220.0 235.0 240.0) "12.0" "280.0")
  (command "CYLINDER" '(-220.0 -235.0 240.0) "12.0" "280.0")

  (princ "\nConstructing Top Vision Turret...")
  (setvar "CLAYER" "CAMERA")
  (command "BOX" '(205.0 -42.0 695.0) '(260.0 42.0 755.0))
  (command "CYLINDER" '(262.0 -16.0 715.0) "12.0" "25.0")
  (command "CYLINDER" '(262.0 16.0 715.0) "12.0" "25.0")

  (princ "\nConstructing Rear Drone Docking Station & Surveillance Quadcopter...")
  (setvar "CLAYER" "DRONE_DOCK")
  (command "BOX" '(-300.0 -180.0 665.0) '(20.0 180.0 675.0))
  (setvar "CLAYER" "DRONE")
  (command "BOX" '(-185.0 -42.0 712.0) '(-95.0 42.0 742.0))
  (command "CYLINDER" '(-70.0 70.0 726.0) "12.0" "22.0")
  (command "CYLINDER" '(-70.0 -70.0 726.0) "12.0" "22.0")
  (command "CYLINDER" '(-210.0 70.0 726.0) "12.0" "22.0")
  (command "CYLINDER" '(-210.0 -70.0 726.0) "12.0" "22.0")

  (princ "\nConstructing Retractable Soil Probe...")
  (setvar "CLAYER" "SOIL_PROBE")
  (command "BOX" '(65.0 45.0 240.0) '(95.0 75.0 450.0))
  (command "CYLINDER" '(80.0 70.0 100.0) "7.0" "160.0")

  (princ "\nConstructing Internal Electronics & LiFePO4 Battery...")
  (setvar "CLAYER" "BATTERY")
  (command "BOX" '(-180.0 -135.0 425.0) '(100.0 135.0 485.0))
  (setvar "CLAYER" "ELECTRONICS")
  (command "BOX" '(-140.0 -145.0 495.0) '(140.0 145.0 565.0))

  (princ "\nConfiguring 3D Visual Style and Isometric Viewport...")
  (command "-VPOINT" "1" "-1" "1")
  (command "ZOOM" "E")
  (command "VSMINTERNAL" "Shaded")
  (setvar "OSMODE" oldosmode)
  (setvar "CMDECHO" oldecho)
  (princ "\n[SUCCESS] AgriBot-X High-Clearance Strut 3D Model Successfully Built in AutoCAD!")
  (princ)
)

(princ "\nAgriBot-X High-Clearance Strut Loaded. Type BUILD_AGRIBOT to construct the 3D model.")
(princ)
